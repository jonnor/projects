# Copyright 2015, Jon Nordby <jononor@gmail.com>. Licensed MIT & LGPLv2+
#
# scaleReference:
# Given a selection of an ImagePlane and a draft Line,
# rescales the ImagePlane to make the distance between two points of the Line
# match a given real-life distance.
# The draft Line is then deleted.

import FreeCADGui
script = "scaleReference"

def show(title=None, text=None):
    title = script if title is None else title
    text = title if text is None else text
    from PySide import QtGui
    QtGui.QMessageBox.information(None, title, text)

def getInput(title=None, text=None, default=0.0):
    title = script if title is None else title
    text = title if text is None else text
    from PySide import QtGui
    val = QtGui.QInputDialog.getDouble(None, title, text, default)
    return val

def isImagePlane(obj):
    return hasattr(obj, "XSize")

def scaleReference():

    # Extract objects from in selection
    selection = FreeCADGui.Selection.getSelection()
    if len(selection) != 2:
        show(text="Expected 2 selected objects, got %d" % (len(selection),))
        return
    
    image, line = None, None
    if isImagePlane(selection[0]):
        image, line = selection
    else:
        line, image = selection
    
    # Current and actual/desired lengths
    current = line.Start.distanceToPoint(line.End)
    actual, ok = getInput(title="Actual length")
    if not ok:
        # User aborted
        return

    # Calculate scaling and apply
    scale = actual/current
    image.XSize = image.XSize*scale
    image.YSize = image.YSize*scale
    line.Document.removeObject(line.Name)

scaleReference()
