from PyQt4 import QtGui, QtCore

# TODO: make configurable
doc = App.ActiveDocument
path = doc.Sketch
#obj = doc.Cylinder
obj = doc.getObject("Part__Feature003")
obj2 = doc.getObject("Part__Feature004")
steps = 10

#geometry = sorted(path.Geometry, key=lambda g: g.discretize(10)[0].x)
geometry = path.Geometry

all = []

for geom in geometry:
	points = geom.discretize(steps)
	for p in points:
		all.append(p)

all = sorted(all, key=lambda p: p.x)

#for p in all[0:len(all)]:
#	obj.Placement.Base = p

def move(rel):
	p = all[int(rel*(len(all)-1))]
#	obj.Placement.Base = App.Vector(p.x, p.z, p.y)
#	obj.Placement.Base = App.Vector(0, 0, p.y)
	z = p.y
	obj.Placement.Base = App.Vector(p.x, obj.Placement.Base.y, z)
	obj2.Placement.Base = App.Vector(p.x+12, obj2.Placement.Base.y, obj2.Placement.Base.z)

i=0
def engine():
	global i
	i+=0.05
	if i > 1.0:
		i = 0.0
	move(i)

#move(0.5)

timer=QtCore.QTimer()
timer.timeout.connect(engine)
timer.start(100)
